// Test filters (for now filters is also dumped with -d - like a debug option)
module snips {
    namespace 'snips';
    prefix 's';

    container C1 {
        presence true;
        list L1 {
            key k;
            leaf k {
                tailf:hidden internal; // remove me
                type string;
            }
            leaf j {
                tailf:info "Helloj";
                type string;
            }
        }

        container C2 {
            tailf:hidden internal; // remove me
        }

        leaf j2 {
            tailf:info "HelloJ2";
            type uint32;
        }
    }


    container COpData {
      tailf:cdb-oper {
        tailf:persistent true;
      }
      list L2 {
         key k;
         leaf-list pathme {
             type string;
         }
         leaf k { type string; }
         leaf l { type string; }
         container InL2  {
           container CO {
              leaf q { type string; }
           }
         }
      }
    }

    list forlater {
       key k;
       leaf k {type string;}
       leaf j {type int32;}
    }
}

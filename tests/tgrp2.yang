module tgrp2 {
  namespace 't.g2';
  prefix 't2';

  include sub-grp;

  grouping Ginner1 {
      leaf gi1 {type string;}
  }
  grouping Ginner2 {
      leaf gi2 {type string;}
  }

  grouping Goutest {
      container InsideGoutest {
          some:non-leaf;
          some:info "";
          some:help
            "msg"+
            "msg2";
          some:last "msg3";
          leaf go1 { type uint32; }
          container InG1 {
              uses Ginner1;
          }
          leaf go2 { type uint32; }

          uses Ginner2;
      }
  }
 
  container C1 {
     uses Gtst;
     leaf l3 { type string; }
  }

  container top {
      uses Goutest;
  }
}
